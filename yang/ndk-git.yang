module ndk-git {
    yang-version "1.1";

    // namespace
    namespace "urn:srl_sdk_apps/nd-kgit";
    prefix "srl_sdk_apps-ndk-git";

    // imports
    import srl_nokia-common {
        prefix srl_nokia-comm;
    }
    import srl_nokia-network-instance {
        prefix srl-netinst;
    }
    import srl_nokia-extensions {
      prefix srl-ext;
    }

    // description
    description
        "This module defines configuration and operational state data related to the git agent.";

    // revision
    revision "2020-09-18" {
        description
          "ndk-git 0.0.1";
    }

    grouping ndk-git-top {
        description
            "Top-level grouping for the git app";
        
        container git-client {
            presence "presence container";
            description
                "Top-level enclosing container for git app
                 Config and operational state data";
            uses git-client-config;
            uses git-client-state;
        }
    }

    grouping git-client-config {
        description
            "Common Configuration for git";
        leaf network-instance {
            default "mgmt";
            type leafref {
                path "/srl-netinst:network-instance/srl-netinst:name";
            }
            description
                "Reference to a configured network-instance used for reachability to the server

                This network-instance must already exist in the system, and different servers within the same server-group may use difference network-instances for connectivity.";
        }
        leaf organization {
            type string {
                // Add all accepted characters here
                pattern "[A-Za-z0-9 !@#$%^&()|+=`~.,'/_:;?-]*";
                length "0..255";
            }
            description
                "Organization where your repo belongs to";
        }
        leaf owner {
            type string {
                // Add all accepted characters here
                pattern "[A-Za-z0-9 !@#$%^&()|+=`~.,'/_:;?-]*";
                length "0..255";
            }
            description
                "Owner where your repo belongs to";
        }
        leaf repo {
            type string {
                // Add all accepted characters here
                pattern "[A-Za-z0-9 !@#$%^&()|+=`~.,'/_:;?-]*";
                length "0..255";
            }
            description
                "The repository that is used in git to store the configuration files in";
        }
        leaf filename {
            type string {
                // Add all accepted characters here
                pattern "[A-Za-z0-9 !@#$%^&()|+=`~.,'/_:;?-]*";
                length "0..255";
            }
            description
                "The filename that is used in the git repo to store your configuration in";
        }

        leaf token {
            type string {
                 // Add all accepted characters here
                 pattern "[A-Za-z0-9 !@#$%^&()|+=`~.,'/_:;?-]*";
                 length "0..255";
            }
            description
                "The github token used to authenticate you to github";
            //type string {
            //    srl-ext:generated-class-name "SecretKey";
            //}
            //description
            //    "The unencrypted shared key used between the client and server";
        }
        leaf author {
            type string {
                // Add all accepted characters here
                pattern "[A-Za-z0-9 !@#$%^&()|+=`~.,'/_:;?-]*";
                length "0..255";
            }
            description
                "The author name used in the commit";
        }
        leaf author-email {
            type string {
                // Add all accepted characters here
                pattern "[A-Za-z0-9 !@#$%^&()|+=`~.,'/_:;?-]*";
                length "0..255";
            }
            description
                "The author email used in the commit";
        }
        leaf branch {
            type string {
                // Add all accepted characters here
                pattern "[A-Za-z0-9 !@#$%^&()|+=`~.,'/_:;?-]*";
                length "0..255";
            }
            description
                "The branch that is used to commit your files to";
        }
    }

    grouping git-client-state {
        description
            "Common State for git";
        leaf oper-state {
            type srl_nokia-comm:oper-state;
            default "down";
            description
              "Details the operational state of the git connection";
            config false;
        }
        container statistics {
            config false;
            description
                "git statistics";
            leaf success {
                type srl_nokia-comm:zero-based-counter64;
                description
                    "The total number of successful git transactions";
            }
            leaf failure {
                type srl_nokia-comm:zero-based-counter64;
                description
                    "The total number of failed git transactions";
            }
        }
    }

    // data definition statements
    uses ndk-git-top;
}
