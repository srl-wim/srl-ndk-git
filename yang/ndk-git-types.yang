module ndk-git-types {
    yang-version 1.1;

    // namespace
    namespace "urn:srl_sdk_apps/ndk-git-types";
    prefix "srl_sdk_apps-ndk-git-types";

    description
        "This module defines shared types for data related to git.";

    // revision
    revision "2020-09-20" {
        description
            "ndk-git-types 0.0.1";
    }

    typedef action-type {
        type enumeration {
            enum "branch" {
                value "0";
                description
                    "Specifies branch action";
            }
            enum "commit" {
                value "1";
                description
                    "Specifies commit action";
            }
            enum "pull-request" {
                value "2";
                description
                    "Specifies pull request action";
            }
        }
        description
            "Git action type";
    }
}
